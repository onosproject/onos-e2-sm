-- **************************************************************
-- E2SM-MHO
-- Information Element Definitions
--
-- **************************************************************

E2SM-MHO-IEs {
iso(1) identified-organization(3) dod(6) internet(1) private(4) enterprise(1) e2(1) version1 (2) e2sm(2) e2sm-MHO-IEs (101)}

DEFINITIONS AUTOMATIC TAGS ::=

BEGIN

IMPORTS
	RANfunction-Name,
    FiveQI,
    CGI,
    UEID,
    RIC-Style-Type,
    RIC-Style-Name,
    RIC-Format-Type

FROM E2SM-COMMON-IEs;

RSRP ::= INTEGER (-65536..65536, ...)

-- **************************************************************
--
-- Lists
--
-- **************************************************************

maxofMessageProtocolTests          INTEGER ::= 15
maxofRICstyles                     INTEGER ::= 63
maxPLMN                            INTEGER ::= 12 -- Maximum number of PLMNs broadcast and reported by UE at establishment
maxNR                              INTEGER ::= 4096


-- **************************************************************
-- E2SM-MHO Common IEs
-- **************************************************************
RIC-Control-Message-Priority ::= INTEGER (0..255, ...)

MHO-Trigger-Type ::= ENUMERATED{
    periodic,
    upon-rcv-meas-report,
    upon-change-rrc-status,
    ...
}

-- **************************************************************
-- Event Trigger Definition OCTET STRING contents
-- **************************************************************

-- E2SM-MHO-EventTriggerDefinition IE
E2SM-MHO-EventTriggerDefinition ::= SEQUENCE{
    eventDefinition-formats    CHOICE{
     eventDefinition-Format1 E2SM-MHO-EventTriggerDefinition-Format1,
        ...
    },
    ...
}

E2SM-MHO-EventTriggerDefinition-Format1 ::= SEQUENCE{
   triggerType                  MHO-Trigger-Type,
   reportingPeriod-ms          INTEGER  OPTIONAL,
   ...
}

-- **************************************************************
-- Indication Header OCTET STRING contents
-- **************************************************************

-- E2SM-MHO-IndicationHeader IE
E2SM-MHO-IndicationHeader ::= CHOICE {
   indicationHeader-Format1             E2SM-MHO-IndicationHeader-Format1,
   ...
}

-- E2SM-MHO-IndicationHeader Format 1
E2SM-MHO-IndicationHeader-Format1 ::= SEQUENCE {
    cgi         CGI,
    ...
}

-- **************************************************************
-- Indication Message OCTET STRING contents
-- **************************************************************

-- E2SM-MHO-IndicationMessage IE
E2SM-MHO-IndicationMessage ::= CHOICE {
   indicationMessage-Format1            E2SM-MHO-IndicationMessage-Format1,
   indicationMessage-Format2            E2SM-MHO-IndicationMessage-Format2,
   ...
}



-- E2SM-MHO-IndicationMessage-Format 1 IE
-- for UE measurement reports
E2SM-MHO-IndicationMessage-Format1 ::= SEQUENCE {
   ueID       UEID,
   measReport  SEQUENCE (SIZE (1..100)) OF E2SM-MHO-MeasurementReportItem,
   ...
}

-- Measured RSRP for a cell
E2SM-MHO-MeasurementReportItem ::= SEQUENCE {
   cgi         CGI,
   rsrp        RSRP,
   fiveQI      FiveQI   OPTIONAL,
   ...
}

-- E2SM-MHO-IndicationMessage-Format 2 IE
-- for UE RRC status
E2SM-MHO-IndicationMessage-Format2 ::= SEQUENCE {
   ueID       UEID,
   rrcStatus   RRCStatus,
   ...
}

RRCStatus ::= ENUMERATED {connected, inactive, idle, ...} 


-- **************************************************************
-- Control Header OCTET STRING contents
-- **************************************************************

-- E2SM-MHO-ControlHeader IE
E2SM-MHO-ControlHeader ::= CHOICE{
    controlHeader-Format1        E2SM-MHO-ControlHeader-Format1,
    ...
}

-- E2SM-MHO-ControlHeader Format 1
E2SM-MHO-ControlHeader-Format1 ::= SEQUENCE{
    rc-command                   MHO-Command,
    ric-Control-Message-Priority    RIC-Control-Message-Priority    OPTIONAL,
    ...
}

MHO-Command::= ENUMERATED {initiateHandover, ... }


-- **************************************************************
-- Control Message OCTET STRING contents
-- **************************************************************

-- E2SM-MHO-ControlMessage IE
E2SM-MHO-ControlMessage ::= CHOICE{
    controlMessage-Format1    E2SM-MHO-ControlMessage-Format1,
...
}

-- E2SM-MHO-ControlMessage Format 1
E2SM-MHO-ControlMessage-Format1 ::= SEQUENCE{
    serving-cgi                 CGI,
    uedID                    UEID,
    target-cgi                CGI,
    ...
}

-- ***************************************************************
-- RAN Function Description OCTET STRING contents
-- ***************************************************************

-- E2SM-MHO-RANfunction-Description
E2SM-MHO-RANfunction-Description ::= SEQUENCE{
    ranFunction-Name    RANfunction-Name,
    e2SM-MHO-RANfunction-Item SEQUENCE{
        ric-EventTriggerStyle-List    SEQUENCE (SIZE(1..maxofRICstyles)) OF RIC-EventTriggerStyle-List OPTIONAL,
        ric-ReportStyle-List    SEQUENCE (SIZE(1..maxofRICstyles)) OF RIC-ReportStyle-List OPTIONAL,
        ...
    },
    ...
}

RIC-EventTriggerStyle-List ::= SEQUENCE{
    ric-EventTriggerStyle-Type            RIC-Style-Type,
    ric-EventTriggerStyle-Name            RIC-Style-Name,
    ric-EventTriggerFormat-Type            RIC-Format-Type,
    ...
}

RIC-ReportStyle-List ::= SEQUENCE{
    ric-ReportStyle-Type                RIC-Style-Type,
    ric-ReportStyle-Name                RIC-Style-Name,
    ric-IndicationHeaderFormat-Type        RIC-Format-Type,
    ric-IndicationMessageFormat-Type    RIC-Format-Type,
    ...
}

END
