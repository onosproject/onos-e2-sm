-- **************************************************************
-- E2SM-RC-PRE
-- Information Element Definitions
--
-- **************************************************************


E2SM-RC-PRE-IEs {
iso(1) identified-organization(3) dod(6) internet(1) private(4) enterprise(1) oran(53148) e2(1) version2 (2) e2sm(2) e2sm-RC-PRE-IEs (100)}

DEFINITIONS AUTOMATIC TAGS ::=

BEGIN

PLMN-Identity ::= OCTET STRING (SIZE(3))

EUTRACellIdentity ::= BIT STRING (SIZE(28))

NRCellIdentity ::= BIT STRING (SIZE(36))

EUTRACGI ::= SEQUENCE {
    pLMN-Identity            PLMN-Identity,
    eUTRACellIdentity        EUTRACellIdentity,
    ...
}

NRCGI ::= SEQUENCE {
    pLMN-Identity            PLMN-Identity,
    nRCellIdentity            NRCellIdentity,
    ...
}

CellGlobalID ::= CHOICE {
    nr-CGI                    NRCGI,
    eUTRA-CGI                EUTRACGI,
    ...
}


EARFCN ::= INTEGER(0..maxEARFCN)
NRARFCN ::= INTEGER(0..maxNRARFCN)
PCI    ::= INTEGER(0..maxPCI)

ARFCN ::= CHOICE {
    eARFCN      EARFCN,
    nrARFCN     NRARFCN
}

Cell-Size ::= ENUMERATED {
   femto, enterprise, outdoorSmall, macro, ... }


-- **************************************************************
--
-- Lists
--
-- **************************************************************

maxofMessageProtocolTests          INTEGER ::= 15
maxofRICstyles                     INTEGER ::= 63
maxPLMN                            INTEGER ::= 12 -- Maximum number of PLMNs broadcast and reported by UE at establishment
maxNR                              INTEGER ::= 4096
maxEARFCN                          INTEGER ::= 262143
maxNRARFCN                         INTEGER ::= 3279167
maxPCI                             INTEGER ::= 1007
maxPciRange                        INTEGER ::= 100
maxofRANparameters                      INTEGER ::= 65535

RIC-Style-Type  ::= INTEGER
RIC-Style-Name  ::= PrintableString(SIZE(1..150,...))
RIC-Format-Type ::= INTEGER


-- **************************************************************
-- E2SM-RC-PRE Common IEs
-- **************************************************************
RIC-Control-Message-Priority ::= INTEGER

RANparameter-Item ::= SEQUENCE {
    ranParameter-ID            RANparameter-ID,
    ranParameter-Value        RANparameter-Value,
    ...
}

RANparameter-ID ::= INTEGER (0..maxofRANparameters)

RANparameter-Value ::= CHOICE{
    valueInt    INTEGER,
    valueEnum    INTEGER,
    valueBool    BOOLEAN,
    valueBitS    BIT STRING,
    valueOctS    OCTET STRING,
    valuePrtS    PrintableString,
    ...
}

RANparameterDef-Item ::= SEQUENCE {
    ranParameter-ID        RANparameter-ID,
    ranParameter-Name        RANparameter-Name,
    ranParameter-Type        RANparameter-Type,
    ...
}

RANparameter-Name ::= PrintableString(SIZE(1..150,...))

RANparameter-Type ::= ENUMERATED{
    integer,
    enumerated,
    boolean,
    bit-string,
    octet-string,
    printable-string,
    ...
}

RC-PRE-Trigger-Type ::= ENUMERATED{
    upon-change,
    periodic,
    ...
}

-- **************************************************************
-- Event Trigger Definition OCTET STRING contents
-- **************************************************************

-- E2SM-RC-PRE-EventTriggerDefinition IE
E2SM-RC-PRE-EventTriggerDefinition ::= SEQUENCE{
    eventDefinition-formats            CHOICE{
        eventDefinition-Format1            E2SM-RC-PRE-EventTriggerDefinition-Format1,
        ...
    },
    ...
}

E2SM-RC-PRE-EventTriggerDefinition-Format1 ::= SEQUENCE{
   triggerType                      RC-PRE-Trigger-Type,
    reportingPeriod-ms                    INTEGER  OPTIONAL,
    ...
}

-- **************************************************************
-- Indication Header OCTET STRING contents
-- **************************************************************

-- E2SM-RC-PRE-IndicationHeader IE
E2SM-RC-PRE-IndicationHeader ::= CHOICE {
   indicationHeader-Format1                E2SM-RC-PRE-IndicationHeader-Format1,
   ...
}

-- E2SM-RC-PRE-IndicationHeader Format 1
E2SM-RC-PRE-IndicationHeader-Format1 ::= SEQUENCE {
    cgi         CellGlobalID    OPTIONAL,
    ...
}

-- **************************************************************
-- Indication Message OCTET STRING contents
-- **************************************************************

-- E2SM-RC-PRE-IndicationMessage IE
E2SM-RC-PRE-IndicationMessage ::= CHOICE {
   ric-Style-Type                          RIC-Style-Type,
   indicationMessage-Format1               E2SM-RC-PRE-IndicationMessage-Format1,
   ...
}

-- E2SM-RC-PRE-IndicationMessage-Format 1 IE
E2SM-RC-PRE-IndicationMessage-Format1 ::= SEQUENCE {
   dl-ARFCN    ARFCN,
   cell-Size   Cell-Size,
   pci         PCI,
   neighbors   SEQUENCE (SIZE(0..maxNR)) OF NRT,
   ...
}

NRT ::= SEQUENCE {
    cgi         CellGlobalID,
    dl-ARFCN    ARFCN,
    cell-Size   Cell-Size,
    pci         PCI,
    ...
}

-- **************************************************************
-- Control Header OCTET STRING contents
-- **************************************************************

-- E2SM-RC-PRE-ControlHeader IE
E2SM-RC-PRE-ControlHeader ::= CHOICE{
    controlHeader-Format1        E2SM-RC-PRE-ControlHeader-Format1,
    ...
}

-- E2SM-RC-PRE-ControlHeader Format 1
E2SM-RC-PRE-ControlHeader-Format1 ::= SEQUENCE{
    cgi         CellGlobalID       OPTIONAL,
    rc-command                       RC-PRE-Command,
    ric-Control-Message-Priority    RIC-Control-Message-Priority    OPTIONAL,
    ...
}

RC-PRE-Command::= ENUMERATED {setParameters, ... }


-- **************************************************************
-- Control Message OCTET STRING contents
-- **************************************************************

-- E2SM-RC-PRE-ControlHeader IE
E2SM-RC-PRE-ControlMessage ::= CHOICE{
    controlMessage        E2SM-RC-PRE-ControlMessage-Format1,
    ...
}

-- E2SM-RC-PRE-ControlMessage Format 1
E2SM-RC-PRE-ControlMessage-Format1 ::= SEQUENCE{
    parameterType            RANparameterDef-Item,
    parameterVal         RANparameter-Value,
    ...
}

-- **************************************************************
-- Control Outcome OCTET STRING contents
-- **************************************************************

-- E2SM-RC-PRE-ControlOutcome IE
E2SM-RC-PRE-ControlOutcome ::= CHOICE{
    controlOutcome-Format1        E2SM-RC-PRE-ControlOutcome-Format1,
    ...
}

-- E2SM-RC-PRE-ControlOutcome Format 1
E2SM-RC-PRE-ControlOutcome-Format1 ::= SEQUENCE{
    outcomeElement-List        SEQUENCE (SIZE(1..maxofRANparameters)) OF RANparameter-Item OPTIONAL,
    ...
}

-- ***************************************************************
-- RAN Function Description OCTET STRING contents
-- ***************************************************************

-- E2SM-RC-PRE-RANfunction-Description
E2SM-RC-PRE-RANfunction-Description ::= SEQUENCE{
    ranFunction-Name    RANfunction-Name,
    e2SM-RC-PRE-RANfunction-Item SEQUENCE{
        ric-EventTriggerStyle-List    SEQUENCE (SIZE(1..maxofRICstyles)) OF RIC-EventTriggerStyle-List OPTIONAL,
        ric-ReportStyle-List        SEQUENCE (SIZE(1..maxofRICstyles)) OF RIC-ReportStyle-List OPTIONAL,
        ...
    },
    ...
}

RANfunction-Name ::= SEQUENCE{
    ranFunction-ShortName       PrintableString(SIZE(1..150,...)),
    ranFunction-E2SM-OID        PrintableString(SIZE(1..1000,...)),
    ranFunction-Description     PrintableString(SIZE(1..150,...)),
    ranFunction-Instance        INTEGER OPTIONAL,
    ...
}

RIC-EventTriggerStyle-List ::= SEQUENCE{
    ric-EventTriggerStyle-Type            RIC-Style-Type,
    ric-EventTriggerStyle-Name            RIC-Style-Name,
    ric-EventTriggerFormat-Type            RIC-Format-Type,
    ...
}

RIC-ReportStyle-List ::= SEQUENCE{
    ric-ReportStyle-Type                RIC-Style-Type,
    ric-ReportStyle-Name                RIC-Style-Name,
    ric-IndicationHeaderFormat-Type        RIC-Format-Type,
    ric-IndicationMessageFormat-Type    RIC-Format-Type,
    ...
}

END
